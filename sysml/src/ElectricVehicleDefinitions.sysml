package ElectricVehicleDefinitions {
	doc
	/*
	 * Electric Vehicle Initial Draft.
	 */

	private import ScalarValues::*;
	private import Quantities::*;
	private import MeasurementReferences::*;
	private import ISQ::*;
	private import SI::*;
	
	/* PART DEFINITIONS */
	
	part def E_Vehicle {
		attribute mass :> ISQ::mass;
		attribute color;
		attribute maxMass :> ISQ::mass;
		attribute requiredBatteryPower :> ISQ::energy;
		attribute currentBatteryLife:> ISQ::energy;
		attribute maxBatteryLife :> ISQ::energy;
		attribute currentMessageFrequency :> ISQ::frequency;
		attribute maximumAcceptedFrequency :> ISQ::frequency;
		attribute currentSpeed:> ISQ::speed;
		attribute maxAcceptedSpeed :> ISQ::speed;
		attribute currentMode: VehicleActionDefinition::Mode;
		attribute primaryEncryption: Encryption;
	}
	
	enum def Encryption {UDP; TCP; I2C; UART; SPI;}
	enum def SecurityModeBluetooth {NONSECURE; SERVICE; LINK;}
	enum def SecurityLevelBluetooth {ONE; TWO; THREE; FOUR;}
	enum def SecurityModeWifi {WPA3; WPA2; WPA_Personal; WEP; OPEN; WPA3_2_Transitional;}
	enum def SecurityMode5G {MUTUAL; SIP;}
		
	constraint def BatteryConstraint;
	constraint def LatencyConstraint;
	constraint def SpeedLimitationConstraint;
	constraint def CameraPixelationConstraint;
	constraint def CameraFOVConstraint;
	constraint def LidarBeamDivConstraint;
	constraint def LidarRangeConstraint;
	constraint def RadarRangeConstraint;
	constraint def GPSAccuracyConstraint;
	constraint def batteryChargeSpeedConstraint;
	constraint def batteryOutputConstraint;
	constraint def massConstraint;
	constraint def telemetryEncryptionConstraint;
	constraint def vehicleMonitoringConstraint;
	constraint def BluetoothSecurityandCountConstraint;
	constraint def WifiSecurityConstraint;
	constraint def Module5GSecurityConstraint;
	constraint def RegularMaintenanceConstraint;
	constraint def sensorAnomalyConstraint;
	constraint def modeLatencyConstraint;
	constraint def modeDisplayConstraint;
	constraint def speedDisplayConstraint;
	constraint def locationDisplayConstraint;
	
	
	/*
	 * Mechanical Components
	 * 
	 */
	part def Transmission {
		attribute mass :> ISQ::mass;	
		attribute driveTrainEfficiency;
	}	
	part def AxleAssembly;
	part def Axle {
		port leftMountingPoint: AxleMountIF;
		port rightMountingPoint: AxleMountIF;
		attribute mass :> ISQ::mass;
	}
	part def Wheel {
		port hub: WheelHubIF;
		attribute mass :> ISQ::mass;
		attribute wheelDiameter :> ISQ::length;
	}
	part def Lugbolt {
		attribute tighteningTorque :> ISQ::torque;
		attribute mass :> ISQ::mass;
	}
	
	/*
	 * Electric Components
	 * 
	 */
	 
	part def processor {
		attribute computationSpeed;
		attribute memory;	
		attribute rating :> ISQ::power;
        
        attribute ProcessorClockRate : FrequencyValue;
	}
	part def CPU :> processor {
        port communication: ComputeCommunicationIF;
        port read: ComputeWithVariableIF;
        port write: ComputeWithVariableIF;
        attribute ProcessorComputePotential;
        attribute storedMemGPSPrevLocation;
    }
	part def GPU :> processor {
        port communication: ComputeCommunicationIF;
        port read: ComputeWithVariableIF;
        port write: ComputeWithVariableIF;
        attribute ProcessorComputePotential;
    }
	part def Battery {
		attribute capacity :> ISQ::energy;
		attribute mass :> ISQ::mass;
		attribute output :> ISQ::power;
		attribute chargeRate;
	}
	 part def HumanDrivingDevices{
    	port manualcontrol: ManualControlIF;
    }
    part def RemoteDevices{
    	port remotecontrol: RemoteControlIF;
    }
    part def Motor{
    	port MotorHub: MotorHubIF;
    	attribute mass :> ISQ::mass;
    	attribute rating :> ISQ::power;
    }
    part def UI {
    	port read: ComputeCommunicationIF;
		attribute rating :> ISQ::power;
		attribute DisplaySpeed :> ISQ::speed;
		attribute currentMode: VehicleActionDefinition::Mode;
    }
	
	/* Sensor Definitions */
	part def Sensor {
		port input: SensorReadIF;
		attribute output :> ISQ::voltage;
		attribute mass :> ISQ::mass;
		attribute latency:> ISQ::time;
	}
	part def GPS :> Sensor {
    	port communication: ComputeCommunicationIF; 
    	attribute rating :> ISQ::power; 
    	attribute range;
    	attribute accuracy;
    	attribute antenna;
    	attribute satelliteCount;
    	attribute augmentationAlgorithms;
    	attribute currentLocation;
    	attribute currentSpeedLimit;
    	attribute frequencyOfUpdates;
	}
	part def Lidar :> Sensor{
    	port communication: ComputeCommunicationIF; 
    	attribute rating :> ISQ::power; 
    	attribute sourceType;
    	attribute wavelength :> ISQ::length;
    	attribute beamDivergence;
    	attribute multiEchoCepacity;
    	attribute range;
	}
	
	part def Radar :> Sensor{
    	port communication: ComputeCommunicationIF; 
    	attribute rating :> ISQ::power; 
    	attribute transmitterPower :> rating;
    	attribute antennaSize;
    	attribute freq :> ISQ::frequency;
    	attribute range;
	}
	
	part def Speedometer :> Sensor{
    	port communication: ComputeCommunicationIF;  
    	attribute rating :> ISQ::power;
    	attribute tireDiameter;
    	attribute frequency :> ISQ::frequency;
	}
	part def Microphone :> Sensor{
    	port communication: ComputeCommunicationIF;  
    	attribute rating :> ISQ::power;
    	attribute frequency :> ISQ::frequency;
	}
	part def Camera :> Sensor{
    	port communication: ComputeCommunicationIF; 
    	attribute rating :> ISQ::power; 
    	attribute fieldOfView;
    	attribute pixelation;
    	attribute frequency :> ISQ::frequency;
	}
	
	part def Controller {
		attribute Mode;
		attribute AcceleratorValue;
		attribute BrakeValue;
		attribute TurnAngle;
		
		port inputCommunication: ComputeCommunicationIF;
		port human: ManualControlIF;
		port remote: RemoteControlIF;
	}
	
	/*Module Definitions */
	doc /* 
	 * Modules are used to ensure added functionality, like 5G, etc that are not sensors, but provide
	 * better computation ability.
	 */
	part def Module{
		attribute input;
		attribute SecurityProtocol;
		attribute BUS_type;
		attribute count;
		port output: ComputeCommunicationIF;
	}
	part def connection_5G :> Module {
		attribute redefines SecurityProtocol: SecurityMode5G;
	}
	part def connection_bluetooth :> Module {
		attribute securityLevel: SecurityLevelBluetooth; 
		attribute redefines SecurityProtocol: SecurityModeBluetooth;  
	}
	part def connection_wifi :> Module {
		attribute redefines SecurityProtocol: SecurityModeWifi;
	}
	
	/* Defining the Autopilot Module */
	
	part def AutonomousDrivingModule {
        
        attribute sensorTypes;
    }
	
	part def DriverDrivingModule{
		part human: HumanDrivingDevices;
		
		attribute Lag;
	}
	
	part def RemoteDrivingModule{
		part remote: RemoteDevices;
		
		attribute Lag;
	}
	
	/* PORT DEFINITIONS */	
	port def DriveIF { 
		in driveTorque :> ISQ::torque;
		attribute ConnectionLag :> ISQ::time;
	}
	
	port def UIToModeSelectIF {
		in userInput;
		out mode;
	}
	
	port def AxleMountIF { 
		inout transferredTorque :> ISQ::torque;
	}
	
	port def WheelHubIF { 
		in appliedTorque :> ISQ::torque;
	}
	
	port def MotorHubIF {
		inout wattage :> ISQ::electricPower;
		attribute ConnectionLag :> ISQ::time;
	}
	
	port def BatteryHubIF {
		out wattage :> ISQ::electricPower;
		attribute ConnectionLag :> ISQ::time;
	}
	
	port def SensorReadIF {
		out voltage :> ISQ::voltage;
		attribute ConnectionLag :> ISQ::time;
		attribute count;
		attribute outType;
	}
	
	port def ComputeWithVariableIF {
		inout voltage :> ISQ::voltage;
		attribute ConnectionLag :> ISQ::time;
	}
	
	port def ComputeCommunicationIF{
		inout dataRate;
        inout dataType;
        inout data;
        attribute ConnectionLag :> ISQ::time;
	}
	
	port def ManualControlIF {
    	inout accelerator :> ISQ::force;  
   	 	inout brake :> ISQ::force;  
    	inout turn :> SI::degree;  
    	attribute ConnectionLag :> ISQ::time;
	}
	
	port def RemoteControlIF {
    	out accelerator :> ISQ::force;
    	out brake :> ISQ::force;
    	out turn :> SI::degree;
    	out signalStrength :> ISQ::power;  
    	attribute ConnectionLag :> ISQ::time;
	}
	
	/* INTERFACE DEFINITIONS */
	
	interface def Mounting {
		doc /* The definition of the interface for mounting a Wheel to an Axle. */
		end axleMount: AxleMountIF;
		end hub: WheelHubIF;
		
		flow axleMount.transferredTorque to hub.appliedTorque;
	}
	
	interface def ComputedPowerSupply {
		doc /* The Overall Definition for power going from battery to motor */
		end battery: BatteryHubIF;
		end sensor: SensorReadIF;
		end motor: MotorHubIF;
		
		flow battery.wattage to motor.wattage;
		flow sensor.voltage to motor.wattage;
	}
	
	interface def motorMovement {
		doc /* 
		 * How the motor is supposed to move, is by converting wattage/current to torque
		 */
		end motor: MotorHubIF;
		end axleMount: AxleMountIF;
		
		flow motor.wattage to axleMount.transferredTorque;
	}
	
	interface def SensorHandle {
		doc /* 
		 * Handling reading sensor and outputting compute voltage
		 */
		end SensorInput: SensorReadIF;
		end read: ComputeWithVariableIF;
		
		flow SensorInput.voltage to read.voltage;
	} 
	
	interface def Forward {
		doc /* Handling reading sensor and outputting compute voltage */
		end compute1: ComputeCommunicationIF;
		end compute2: ComputeCommunicationIF;
		
		flow compute1.dataRate to compute2.dataRate;
		flow compute1.dataType to compute2.dataType;
		flow compute1.data to compute2.data;
	}
	
	interface def ActAuto {
		doc /* Acting on input */
		end input: ComputeCommunicationIF;
		end output: ManualControlIF;
		
		flow input.data to output.accelerator;
		flow input.data to output.brake;
		flow input.data to output.turn;
	}
	
	interface def ActManual {
		doc /* Acting on input */
		end input: ManualControlIF;
		end output: ManualControlIF;
		
		flow input.accelerator to output.accelerator;
		flow input.brake to output.brake;
		flow input.turn to output.turn;
	}
	
	interface def ActRemote {
		doc /* Acting on INput */
		end input: RemoteControlIF;
		end output: ManualControlIF;
		
		flow input.accelerator to output.accelerator;
		flow input.brake to output.brake;
		flow input.turn to output.turn;
	}
	
	interface def controlMotor {
		doc /* Handling Motor Control */
		end input: ComputeWithVariableIF;
		end motor: MotorHubIF;
		
		flow input.voltage to motor.wattage;
	}
	
}
