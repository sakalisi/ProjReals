package ElectricVehicleUsages {
	doc
	/*
	 * usages of elements from the Electric vehicle definitions model.
	 */

	private import SI::N;
	private import SI::m;
	private import SI::kg;
	private import SI::kW;
	private import SI::W;
	private import SI::s;
	private import ScalarFunctions::*;

	public import ElectricVehicleDefinitions::*;

	/* VALUES */	 
	T1 = 10.0 [N * m];
	T2 = 20.0 [N * m];
	LugboltMass = 0.04 [kg];
	WheelMass = 25 [kg];
	MotorMass = 250 [kg];
	BatteryMass = 2000 [kg];
	AxleMass = 90 [kg];
	SensorRating = 0.01 [W]; 
	BatteryLife = 1000 [kW * s * 3600];
	CPUrating = 10 [kW * s * 3600];
	GPUrating = 10 [kW * s * 3600];
	
	
	/* PARTS */	
	part narrowRimWheel: Wheel {
		doc /* Narrow-rim wheel configuration with 4 to 5 lugbolts. */

		part lugbolt: Lugbolt[4..5];
	}
	
	part wideRimWheel: Wheel {
		doc /* Wide-rim wheel configuration with 4 to 6 lugbolts. */	

		part lugbolt: Lugbolt[4..6];
	}

	part vehicle_C1: E_Vehicle {
		doc /* Basic Vehicle configuration showing a part hierarchy. */

		part frontAxleAssembly: AxleAssembly {
			part frontWheel[2] subsets narrowRimWheel {
				part redefines lugbolt[4] {
					attribute redefines tighteningTorque = T1;
					attribute redefines mass = LugboltMass;
				}
				attribute redefines mass = WheelMass;
			}
			part frontAxle: Axle {
				attribute redefines mass = AxleMass;	
			}
			
		}		
		part rearAxleAssembly: AxleAssembly {
			part rearWheel[2] subsets wideRimWheel {
				part redefines lugbolt[6] {
					attribute redefines tighteningTorque = T2;
					
					attribute redefines mass = LugboltMass;
				}
				attribute redefines mass = WheelMass;
			}
			part rearAxle: Axle {
				attribute redefines mass = AxleMass;	
			}			
		}
		
		part motor_C3[4]: Motor {
			port motorHub: MotorHubIF;
			attribute redefines mass = MotorMass;
		}
	}
	
	part vehicle_C2 subsets vehicle_C1 {
		doc /* Specialized configuration with part-specific ports. */
		
		part redefines frontAxleAssembly {
			part leftFrontMotor subsets motor_C3 = motor_C3#(1);
			part rightFrontMotor subsets motor_C3 = motor_C3#(2);
			part leftFrontWheel subsets frontWheel = frontWheel#(1);
			part rightFrontWheel subsets frontWheel = frontWheel#(2);
			
			interface leftFrontMount: Mounting connect 
				frontAxle.leftMountingPoint to leftFrontWheel.hub;
			interface leftFrontMove: motorMovement connect
				leftFrontMotor.motorHub to frontAxle.leftMountingPoint;
			interface rightFrontMount: Mounting connect 
				frontAxle.rightMountingPoint to rightFrontWheel.hub;
			interface RightFrontMove: motorMovement connect
				rightFrontMotor.motorHub to frontAxle.rightMountingPoint;
		}
		
		part rearAxleAssembly redefines vehicle_C1::rearAxleAssembly {
			part leftRearMotor subsets motor_C3 = motor_C3#(3);
			part rightRearMotor subsets motor_C3 = motor_C3#(4);
			part leftRearWheel subsets rearWheel = rearWheel#(1);
			part rightRearWheel subsets rearWheel = rearWheel#(2);

			interface leftRearMount: Mounting connect 
				rearAxle.leftMountingPoint to leftRearWheel.hub;
			interface leftRearMove: motorMovement connect
				leftRearMotor.motorHub to rearAxle.leftMountingPoint;
			interface rightRearMount: Mounting connect 
				rearAxle.rightMountingPoint to rightRearWheel.hub;
			interface rightRearMove: motorMovement connect
				rightRearMotor.motorHub to rearAxle.rightMountingPoint;
		}		
	}
	
	part vehicle_C3 subsets vehicle_C2 {
		doc /* Further specialized configuration with a connection to a deeply-nested port. */
		
		part LIDAR: Lidar;
		part RADAR: Radar;
		part SPD_Meter: Speedometer;
		part Mic: Microphone;
		part Cams: Camera [3];
		part GPS_Module: GPS;
		
		part cpu: CPU;
        part gpu: GPU;
        part controller: Controller;
        part module: Module;
        part ui: UI;
		
		part c5g: connection_5G;
		part cw: connection_wifi;
		part cb: connection_bluetooth;
		
		part batt: Battery;
		
		part transmission: Transmission {
			port drive: ~DriveIF;
		}
		
		part redefines rearAxleAssembly {
			part redefines rearAxle {
				port drive: DriveIF;
			}
		}
		part redefines frontAxleAssembly {
			part redefines frontAxle {
				port drive: DriveIF;
			}
		}
		
		interface reardriveShaft connect 
			transDrive ::> transmission.drive to axleDrive ::> rearAxleAssembly.rearAxle.drive {
			flow transDrive.driveTorque to axleDrive.driveTorque;
		}
		interface forwarddriveShaft connect 
			transDrive ::> transmission.drive to axleDrive ::> frontAxleAssembly.frontAxle.drive {
			flow transDrive.driveTorque to axleDrive.driveTorque;
		}
		
		
		
		
	}
	
	part E_Vehicle_Automatic subsets vehicle_C3 {
		part AutonomousDrive: AutonomousDrivingModule {
			
			interface HandleLIDAR: SensorHandle connect
				vehicle_C3.LIDAR.input to vehicle_C3.cpu.read;
			interface HandleRADAR: SensorHandle connect
				vehicle_C3.RADAR.input to vehicle_C3.cpu.read;
			interface HandleSPD_Meter: SensorHandle connect
				vehicle_C3.SPD_Meter.input to vehicle_C3.cpu.read;
			interface HandleMic: SensorHandle connect
				vehicle_C3.Mic.input to vehicle_C3.cpu.read;
			interface HandleCams: SensorHandle connect
				vehicle_C3.Cams.input to vehicle_C3.cpu.read;
			interface CNNInterface: Forward connect
				vehicle_C3.cpu.communication to vehicle_C3.gpu.communication;
			interface Act: ActAuto connect
				vehicle_C3.gpu.communication to vehicle_C3.controller.inputCommunication;
			interface UIComs: Forward connect
				vehicle_C3.cpu.communication to vehicle_C3.ui.read;
			interface motorCtrl: controlMotor connect
				vehicle_C3.gpu.write to vehicle_C3.motor_C3.motorHub;
		}	
	}
		
	part E_Vehicle_Manual subsets vehicle_C3 {
		part HumanDrive: DriverDrivingModule {
			
			interface HandleRADAR: SensorHandle connect
				vehicle_C3.RADAR.input to vehicle_C3.cpu.read;
			interface HandleSPD_Meter: SensorHandle connect
				vehicle_C3.SPD_Meter.input to vehicle_C3.cpu.read;
			interface HandleCams: SensorHandle connect
				vehicle_C3.Cams.input to vehicle_C3.cpu.read;
			interface actMan: ActManual connect
				human.manualcontrol to vehicle_C3.controller.human;
			interface UIComs: Forward connect
				vehicle_C3.cpu.communication to vehicle_C3.ui.read;
			interface motorCtrl: controlMotor connect
				vehicle_C3.cpu.write to vehicle_C3.motor_C3.motorHub;
		}	
	}
	
	part E_Vehicle_Remote subsets vehicle_C3 {
		part RemoteDrive: RemoteDrivingModule {
			
			interface HandleRADAR: SensorHandle connect
				vehicle_C3.RADAR.input to vehicle_C3.cpu.read;
			interface HandleSPD_Meter: SensorHandle connect
				vehicle_C3.SPD_Meter.input to vehicle_C3.cpu.read;
			interface HandleCams: SensorHandle connect
				vehicle_C3.Cams.input to vehicle_C3.cpu.read;
			interface transmitComs5G: Forward connect
				vehicle_C3.c5g.output to vehicle_C3.cpu.communication;
			interface transmitComsWifi: Forward connect
				vehicle_C3.cw.output to vehicle_C3.cpu.communication;
			interface transmitComsBluetooth: Forward connect
				vehicle_C3.cb.output to vehicle_C3.cpu.communication;
			interface actMan: ActManual connect
				vehicle_C3.cpu.communication to vehicle_C3.controller.remote;
			interface UIComs: Forward connect
				vehicle_C3.cpu.communication to vehicle_C3.ui.read;
			interface motorCtrl: controlMotor connect
				vehicle_C3.cpu.write to vehicle_C3.motor_C3.motorHub;
		}	
	}	
	
	part E_VehicleTotal subsets E_Vehicle_Remote, E_Vehicle_Automatic, E_Vehicle_Manual{
			attribute redefines primaryEncryption = Encryption::UDP;
	}

}
